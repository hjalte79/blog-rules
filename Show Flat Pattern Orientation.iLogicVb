' Show Flat Pattern Orientation
' Code written by: Jelte de Jong
' http://www.hjalte.nl/21-show-flat-pattern-orientation
Dim doc As PartDocument = ThisDoc.Document
Dim def As SheetMetalComponentDefinition = doc.ComponentDefinition
Dim oTr As TransientObjects = ThisApplication.TransientObjects

If (def.HasFlatPattern = False) Then Return
def.FlatPattern.Edit()

Dim topFace As HighlightSet = doc.HighlightSets.Add()
topFace.Color = oTr.CreateColor(0, 255, 0, 0.1)
topFace.AddItem(def.FlatPattern.TopFace)

Dim upBendEdges As HighlightSet = doc.HighlightSets.Add()
upBendEdges.Color = oTr.CreateColor(0, 0, 255)

Dim downBendEdges As HighlightSet = doc.HighlightSets.Add()
downBendEdges.Color = oTr.CreateColor(255, 0, 0)

For Each res As FlatBendResult In def.FlatPattern.FlatBendResults
    If (res.IsDirectionUp) Then
        upBendEdges.AddItem(res.Edge)
    Else
        downBendEdges.AddItem(res.Edge)
    End If
Next

ThisApplication.CommandManager.Pick(
	SelectionFilterEnum.kAllEntitiesFilter,
        "Press esc or select anything.")
topFace.Clear()
upBendEdges.Clear()
downBendEdges.Clear()
